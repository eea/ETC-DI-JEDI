FME workspace RemoveNBITS_and_nodata_setter_v1 .fmw
Title: RemoveNBITS

Parameters:
- SourceDataset_GEOTIFF = S:\Common workspace\ETC_DI\f03_JEDI_PREPARATION\f01_dims\ESA_CCI_AGB\v4\2019-2018\clipper\ESA_CCI_AGB_2019_2018_SD.tif   # Source GeoTIFF File(s)
- DestDataset_GEOTIFF = S:\Common workspace\ETC_DI\f03_JEDI_PREPARATION\f01_dims\ESA_CCI_AGB\v4\2019-2018\nbit   # Destination GeoTIFF Folder
- NODATA_VALUE = -9999   # Nodata Value

Readers:
- GEOTIFF_1: GEOTIFF from $(SourceDataset_GEOTIFF) in EPSG:3035

Writers:
- GEOTIFF_2: GEOTIFF to $(DestDataset_GEOTIFF)

GEOTIFF (reader GEOTIFF_1)
    attributes: datatype char(255)
    -> RasterPropertyExtractor_2
RasterPropertyExtractor_2
    -> AttributeExposer_2
Note: Get CompressionMethod and geotiff_number_of_bits_per_cell (NBITS)
AttributeExposer_2
    ATTR_LIST = geotiff_number_of_bits_per_cell
    -> AttributeRemover_4
Note: Remove geotiff_number_of_bits_per_cell (NBITS) attribute. (This prevents geotrellis errors)
AttributeRemover_4
    REMOVE_ATTRS = geotiff_number_of_bits_per_cell
    -> RasterBandNodataSetter
RasterBandNodataSetter
    NODATA_VALUE = $(NODATA_VALUE)
    REPLACE_CELL_VALUES = Yes
    -> GEOTIFF (writer GEOTIFF_2)
GEOTIFF (writer GEOTIFF_2)
    attributes: datatype char(255)
