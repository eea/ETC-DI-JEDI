FME workspace s01_s02_pa_testings_v2.fmw

Parameters:
- datasetURL = https://cwsblobstorage01.blob.core.windows.net/cwsblob01/ExportTable/nuts3/PA2022_21_indicator/part-00000-tid-1325046920122742987-cd1b109f-274e-4c17-9adb-cccc57e553c2-1399-1-c000.csv.gz   # Define URL to dataset to be downloaded
- database_table_name = test2   # Please enter the name for the table in MS-SQL
- outputFolder = S:\Common workspace\ETC_DI\f01_TASK_DATA\ETC_DI_2022\WP3_data_intelligence\AP22_3_1_1_Azure_data_bricks\data\DATA_from_AZURE\nuts3\D1_drought\D1_1_avg_drought_pressure_intensity   # Define path to output folder
- Schema_database = demo   # schema_database
- DestDataset_MSSQL_ADO = greenmonkey  Carbon_Mapping   # SQL Server Connection
- DestDataset_MSSQL_JDBC_NONSPATIAL_2 = greenmonkey climate impact   # SQL Server (JDBC) Connection
- zip = .zip

Writers:
- MSSQL_ADO_1: MSSQL_ADO to $(DestDataset_MSSQL_ADO)
- MSSQL_JDBC_NONSPATIAL_2_1: MSSQL_JDBC_NONSPATIAL_2 to $(DestDataset_MSSQL_JDBC_NONSPATIAL_2)

Note: Define URL to Azure file, dataformat and output folder first first!

Bookmark: STARTER
Creator
    GEOMTYPE = Geometry Object
    NUM = 1
    CREATED -> HTTPCaller_download_azureFile

Bookmark: reading from Azure
HTTPCaller_download_azureFile
    CONNECTION_TIMEOUT_LENGTH = 60
    ERROR_ATTR = _error
    FILE_PATH_ATTR = _response_file_path
    FOLLOW_REDIRECTS = FOLLOW_WITH_GET
    HTTP_METHOD = GET
    OUTPUT_FILENAME = $(outputFolder)/import.zip
    REDIRECT_AUTH = ORIGINAL_DOMAIN_ONLY
    SAVE_FILE = File
    SAVE_MULTI = No
    STATUS_CODE_ATTR = _http_status_code
    TARGET_URL = $(datasetURL)
    TRANSFER_TIMEOUT_LENGTH = 90
    USE_COOKIES = No
    VERIFY_SSL_CERTIFICATES = Yes
    -> FeatureReader [INITIATOR]

Bookmark: Storing on CW
FeatureReader
    ATTRIBUTES = CSV,"ADM_ID,ADM_country,ICC,LEVEL3_name,LEVEL3_code,NUTS_EU,TAA,pa2022,pa2021,area_ha"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(outputFolder)/import.zip
    FORMAT = CSV2
    INTERACT = NONE
    OUTPUT_FEATURES_DISPLAY = Schema and Data Features
    CSV -> Table1 (writer MSSQL_JDBC_NONSPATIAL_2_1)

Bookmark: Export to MS-sql
Table1 (writer MSSQL_JDBC_NONSPATIAL_2_1)
    attributes: ADM_ID bigint, ADM_country varchar(23), ICC varchar(3), LEVEL3_name varchar(81), LEVEL3_code varchar(8), NUTS_EU varchar(6), TAA varchar(13), pa2022 bigint, pa2021 bigint, area_ha float
Table1 (writer MSSQL_ADO_1)
